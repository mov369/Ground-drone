# Robot_1
Robot_1 will do the work that I don't like doing the most - cleaning.
The requierements are derived from that.

## 1: Robot Capabilities examples (Container)

### #2: Construction (Container)
Has inbuilt HMI

#### #14: Dimensions (Container)

##### #15: Is not wider than a standard delivery box (Functional)

##### #22: Is not longer than a standard delivery driver on a bicycle / (Functional)

#### #21: Modularity (Functional)
UGV shall be constructed in modular components for easy spare part procurement and replacement

### #3: Communications (Container)
Can be controlled remotely using a PC/Laptop

#### #9: Flight Control (Functional)
UGV shall provide a dedicated and permanent communications link for command and control for all the range of operations

#### #12: Payload (Functional)
UGV shall provide a dedicated and permanent payload data link for all the range of operations

### #6: Roadworthiness (Container)

#### #17: Functional Safety Requirements (Informational)
These will need to be found out.
should fit the 26262 & local Council rules on UGVs on public roads

#### #29: Range (Functional)
The UGV shall be controllable for all distances within line-of-sight

#### #30: Rain Conditions (Functional)
All UGV components shall be able to operate under rain for at least 10 minutes

#### #31: Power (Functional)
UGV shall provide power to operate all onboard systems for the complete duration of the flight

#### #32: Emergency Power (Functional)
In case of power generation failure, UGV shall provide emergency power for up to 20 minutes of flight for all flight-critical systems.

#### #33: Control Surface Fault-Tolerance (Functional)
UGV shall be tolerant to single-servo failures

#### #34: Fuel (Functional)
UGV propulsion shall be capable of operating with 89 Octane Gasoline

#### #35: No Payload Flights (Functional)
UGV shall be able to safely get airborne without a payload

#### #36: Flight Data Recorder (Functional)
UGV shall provide the means to record all flight data from every component on board for the duration of the flight

#### #37: Flight Identification (Functional)
UGV shall provide an ADSB transponder on board for proper identification

#### #38: Lights (Functional)
UGV shall provide aeronautical standard navigation and strobe lights

#### #39: Flight Computer (Functional)
UGV shall provide a flight computer to autonomously conduct safe flight operations from launch to recovery

#### #40: Endurance (Functional)
The UGV shall be able to sustain uninterrupted flights for up to three hours

### #8: Payload Capabilities (Container)
Can carry and house an average parcel

#### #16: Carrying Capacity (Functional)
UGV shall be able to carry up to ___ of payload

#### #18: Payload Bay Capacity (Functional)
UGV shall provide a payload bay with at least ___ cm^3

#### #19: Payload Protection (Functional)
UGV shall be provided with a universal payload-retraction system to protect the payload during takeoff and landing

#### #20: Default Payload (Functional)
UGV shall provide a pre-installed payload in the form of a gimbal-stabilized visual camera providing Full-Motion video.

## 2: Robot Initial Requirements (Functional)

### #42: Robot Path Planning (Functional)

#### #45: Robot shall roam the apartment clockwise, following the left wall (Functional)

#### #50: Robot shall gradually move towards the centre of the apartment, covering the whole area of the floor (Functional)

#### #51: Robot shall put itself to charge once the battery is below 20% (Functional)
Confirm the safe amount of battery charge for Li-ion batteries.

### #43: Robot Components (Functional)

#### #56: Electrical (Functional)

##### #52: Motor (Functional)

##### #53: ESC (Functional)

#### #57: Mechanical (Functional)

##### #54: Impeller (Functional)

##### #58: Electronics Enclosure (Functional)

##### #59: Dirt Chamber (Functional)

### #44: Robot Additional Characteristics (Container)

#### #46: Robot shall produce the least amount of noise possible (Functional)

#### #47: Robot shall have least amount of mass (Functional)

#### #49: Robot shall hold enough charge for 2 full cleans (Functional)
